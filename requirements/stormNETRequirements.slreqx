# stormNETRequirements
StormAD shall have a service-oriented architecture that integrates available 
services from Brainstorm, Freesurfer, BIDS Apps, WSL and remote HPC

StromAD requires new services to be developed for Brainstorm:
 - importing PET data
 - modifying the database for PET data
 - co-registering PET data
 - anatomy computation remotely

## #1: Data Management (Container)
- The system shall store dataset information securely in a database
- The system shall store derivatives information securely in a database
- The system shall store user data securely in a database

### #5: Reads the structure of remote BIDS datasets (Functional)
All metadata will be automatically extracted from the information contained in the BIDS JSON files, and inserted as new Brainstorm data entries for instantaneous availability.

#### #6: The system must handle communications with remote repositories (Informational)
- The system must handle communications with remote repositories

#### #7: The system must read BIDS datasets (Informational)

#### #8: The system must write BIDS Derivatives (Informational)

#### #9: Brainstorm database structure must import new BIDS-multimodal studies (Functional)

### #38: The toolbox shall store the output of StormAD Core statistics in a database (Functional)

#### #39: Vertex-wise measures (Functional)

#### #40: Voxel-wise measures (Functional)

### #41: The toolbox shall store references to StormAD derivative files in a database (Functional)

### #68: Wrapper for local Linux processing (Functional)
- linux runtime manager MATLAB

### #80: Must be able to import PET data into Brainstorm (Functional)

### #86: The data management module shall provide a data catalogue (Functional)

## #2: StormAD shall provide a GUI for exploring and analyzing available data catalogue (Container)
- The system shall provide a graphical user interface (GUI) for user interactions with a data catalogue.
- The system shall ensure the GUI is responsive and works on different screen sizes.
- The system shall integrate Brainstorm GUI functions.

### #44: GUI shall have a dashboard for dataset handling (Functional)

#### #45: UI shall use LORIS API for visualizing remote repositories (Functional)

#### #46: GUI shall have a module for multimodal StormAD format (Functional)
- Rationale: - The GUI shall show only the available data that is required for multimodal analysis in Brainstorm
- Keywords: -

##### #47: Longitudinal (Functional)
- Rationale:
  - visit label
  - anatomy data
  - surface
  - volume
  - mri
  - PET data
  - SUVR
  -tracer
  - MEG data
  - CSD
  - Connectivity
  - Travelling Waves

##### #48: Cross-sectional (Functional)
- Rationale:
  - anatomy data
  - surface
  - volume
  - mri
  - PET data
  - SUVR
  -tracer
  - MEG data
  - CSD
  - Connectivity
  - Travelling Waves

### #50: GUI shall have a dashboard for processing subjects (Functional)

## #3: StormAD Core Functionalities (Container)
- Get subject anatomy
- Co-register modalities

### #17: PET module (Container)

#### #13: The toolbox must import subject PET data - if it is already processed (Functional)

#### #14: The toolbox must process PET data - if this does not already exist (Functional)

#### #15: The toolbox must provide co-registration of PET with structural MR (Functional)

#### #16: The toolbox must allow ROI analysis of PET (Functional)

### #18: Anatomy module (Container)

#### #10: The toolbox must obtain subject anatomy - if it already exists (Functional)

#### #11: The toolbox must process subject anatomy - if it does not already exist (Functional)

#### #64: The toolbox must export ROI-based morphological features (Functional)

#### #65: Detailed analysis of entorhinal, peri-rhinal and hippocampus (Functional)

### #19: MEG module (Container)

#### #20: MEG Current Density Mapping (Functional)

#### #21: MEG preprocessing (Functional)

##### #22: Remove power-line harmonics through notch filtering (Functional)

##### #23: Remove artefacts through ICA (Functional)

###### #24: Identify and remove cardiac artefacts (Functional)

###### #25: Identify and remove eyeblink artefacts (Functional)

#### #26: Register MEG to subject anatomy (Functional)

#### #27: Compute MEG spectral features (Functional)

##### #33: Band power (Functional)

#### #28: Compute MEG connectivity (Functional)

##### #29: Coherence (Functional)

##### #30: Partial coherence (Functional)

##### #31: Phase-locking value (Functional)

##### #32: Granger causality (Functional)

#### #34: MEG Travelling Waves (Functional)

#### #66: MEG regional analysis (Container)

### #35: Statistics module (Container)

#### #36: Structure vertex-wise data from modules (Functional)

##### #42: Each vertex must have an ID as a primary key (Functional)

#### #37: Structure voxel-wise data from modules (Functional)

##### #43: Each voxel must have an ID as a primary key (Functional)

### #51: Cognition module (Container)

### #52: Demographic Module (Container)

### #53: Histology Module (Container)

### #54: Somatomotor module (Container)

### #55: Genetics Module (Container)

### #56: Machine Learning Module (Container)

#### #57: DL model to predict vertex-wise PET data from MEG (Functional)

#### #58: Wrapper for Scikit-learn (Functional)

#### #59: Classification and clustering (Functional)

#### #60: Multivariate models to predict continuous values (Functional)

#### #61: Multimodal biomarkers through longitudinal data (Functional)
- Rationale: Diagnostics and prognostic multimodal biomarkers

#### #62: Exporter for PyTorch (Functional)

## #67: StormAD shall provide processing in remote HPC (Container)
Target Computer
What can be used as a target computer:
- Any Linux machine that supports MATLAB® installation.
- Windows machine with Windows Subsystem for Linux (WSL2 version) installed.
- WSL version 2 is required.
- WSL Linux distros with minimum versions: Ubuntu 18.04/Debian 11/Oracle Linux_7_9 should be setup.
- WSL target should be on the same windows host machine.
For more information, see https://in.mathworks.com/support/requirements/matlab-linux.html
Target Computer Requirements
To deploy Service Oriented Architecture applications on a target computer using the support package, following requirements have to be met.
- Docker software version 20.10 or later needs to be installed.
- Zip and Unzip commands needs to be installed.
- SSH server needs to be in running state.
- Target computer username needs to have privileges to run docker commands. For more information, see https://docs.docker.com/engine/install/linux-postinstall/#manage-docker-as-a-non-root-user.

### #4: User Configuration Module (Functional)
The system must manage user accounts, including login credentials and user preferences for remote data repositories
The system must manage user accounts, including login credentials and user preferences for remote data repositories
Stores and manages user credentials
Configures remote environment (aliases, paths, etc.)
Saves and loads user preferences
- Rationale: User login information is required to access remote repositories and processing pipelines

#### #63: The system shall store curated data for training ML models (Functional)

#### #69: Store remote connection information locally (Informational)
The system must store:
- SSH keys
- remote user account
- remote server name
- remote HPC account name
- remote working directory
- remote dataset directory
- remote derivatives directory

#### #70: The system must store bash files for remote execution (Informational)

### #71: Sync local WSL with remote working directory (Functional)

### #72: Remote execution module (Functional)
Transfers bash scripts to the remote server
Executes scripts on the remote server
Retrieves and displays execution results

#### #73: Pass user enviroment to remote server (Functional)

##### #75: Set working directory alias (Functional)

##### #76: Set dataset directory alias (Functional)

### #74: Feedback messages from remote server (Functional)

### #78: StormRemote GUI for user interactions (Functional)
Provides interface for user interactions
Allows selection of files/scripts to transfer
Displays connection status and execution results

### #79: Local file transfer module (Functional)
For windows users,
Transfers files from Windows to WSL directory
Handles file permissions and path conversions

## #81: Identify critical state for conversion to AD (Functional)
Streams of information that combines data from multiple source to infer **events** or patterns that suggest circumstances:
- critical point at which MCI converts to AD
- identify meaningful events to identify threats
- State control?

## #82: StormAD shall provide PET processsing services (Functional)

## #84: StormAD shall provide tools for longitudinal analysis (Functional)

## #85: StormAD shall provide access to Alzheimer's disease datasets (Functional)
